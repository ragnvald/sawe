FME workspace wilderness_analysis_norge_norway_2019.fmw

Parameters:
- SourceDataset_SHAPE = C:\code\sawe\data_in\global\osm\ne_10m_admin_0_countries.shp   # Source Esri Shape File(s)
- DestDataset_GEOPACKAGE = ../data_out/wilderness_database.gpkg   # GeoPackage File
- SourceDataset_ESRISHAPE_8 = C:\code\sawe\data_in\osm\gis_osm_railways_free_1.shp   # Source Esri Shapefile(s)
- SourceDataset_ESRISHAPE_9 = C:\code\sawe\data_in\osm\gis_osm_waterways_free_1.shp   # Source Esri Shapefile(s)
- SourceDataset_ESRISHAPE_7 = C:\code\sawe\data_in\osm\gis_osm_landuse_a_free_1.shp   # Source Esri Shapefile(s)
- SourceDataset_ESRISHAPE_6 = C:\code\sawe\data_in\osm\gis_osm_roads_free_1.shp   # Source Esri Shapefile(s)
- SourceDataset_ESRISHAPE = C:\code\sawe\data_in\osm\gis_osm_water_a_free_1.shp   # Source Esri Shapefile(s)

Readers:
- SHAPE_1: SHAPE from $(SourceDataset_SHAPE)
- ESRISHAPE_1: ESRISHAPE from $(SourceDataset_ESRISHAPE_8)
- ESRISHAPE_2: ESRISHAPE from $(SourceDataset_ESRISHAPE_9)
- ESRISHAPE_3: ESRISHAPE from $(SourceDataset_ESRISHAPE_7)
- ESRISHAPE_4: ESRISHAPE from $(SourceDataset_ESRISHAPE_6)
- ESRISHAPE_5: ESRISHAPE from $(SourceDataset_ESRISHAPE)

Writers:
- GEOPACKAGE_1: GEOPACKAGE to $(DestDataset_GEOPACKAGE)

gis_osm_water_a_free_1 (reader ESRISHAPE_5)
    attributes: osm_id char(10), code short, fclass char(28), name char(100)
    -> AttributeFilter_7
    -> AttributeFilter_8
AttributeFilter_7
    ATTR_NAME = fclass
    ATTR_VALUES = <Empty>,<Missing>,<Null>,<Unfiltered>,NOR,dock,glacier,reservoir,river,water,wetland
    water -> AttributeRemover_8
AttributeRemover_8
    REMOVE_ATTRS = fclass,SU_DIF,ISO_N3,ISO_A3,NAME,code,MAPCOLOR7,NOTE_ADM0,GDP_YEAR,GEOUNIT,featurecla,UN_A3,NAME_ALT,CONTINENT,ADM0_DIF,ABBREV_LEN,ADM0_A3_UN,INCOME_GRP,ADM0_A3_US,BRK_A3,MAPCOLOR8,SUBUNIT,GU_A3,FIPS_10_,ADM0_A3,GEOU_DIF,name,ABBREV,ECONOMY,FORMAL_FR,POSTAL,LEVEL,osm_id,POP_YEAR,NOTE_BRK,SOVEREIGNT,GDP_MD_EST,SOV_A3,WOE_ID_EH,ADMIN,HOMEPART,WOE_ID,ADM0_A3_WB,LABELRANK,scalerank,SUBREGION,WIKIPEDIA,LASTCENSUS,NAME_LEN,BRK_GROUP,BRK_NAME,POP_EST,TINY,TYPE,BRK_DIFF,NAME_LONG,WB_A3,SU_A3,REGION_UN,LONG_LEN,MAPCOLOR9,WB_A2,NAME_SORT,ADM0_A3_IS,REGION_WB,FORMAL_EN,ISO_A2,MAPCOLOR13,WOE_NOTE
    -> AreaOnAreaOverlayer_2 [AREA]
Note: First b uffer 1000 around all features
B_0-1000_n_2: GeographicBufferer
    ANGLE = 22.5
    BufferDist = 1000
    BufferUnit = Meters
    CAP_STYLE = Round
    CORNER_STYLE = Round
    MITER_LIMIT = 1
    -> Dissolver_2
Note: Wilderness is what is left when encroachment has been removed. This part collects the land area and deletes the established encroachment areas.
GeographicAreaCalculator_2
    AREA_ATTR = area_km2
    AreaMult = 0.000001
    -> AreaOnAreaOverlayer_2 [AREA]
Note: Overlay with workld countries mask and remove those parts being outside the country.
Result_of_calculations: Inspector
wilderness (writer GEOPACKAGE_1)
    attributes: wzone text(1), area_km2 float

Bookmark: Data in
AttributeFilter_8
    ATTR_NAME = fclass
    ATTR_VALUES = <Empty>,<Missing>,<Null>,<Unfiltered>,NOR,dock,glacier,reservoir,river,water,wetland
    dock -> AttributeRemover_11
    reservoir -> AttributeRemover_11
AttributeRemover_11
    REMOVE_ATTRS = name,code,fclass,osm_id,width
    -> B_0-1000_n_2
Note: Inngrepsdata legges inn her
gis_osm_roads_free_1 (reader ESRISHAPE_4)
    attributes: osm_id char(10), code short, fclass char(28), name char(100), ref char(20), oneway char(1), maxspeed short, layer number(12,0), bridge char(1), tunnel char(1)
    -> AttributeFilter_2
AttributeFilter_2
    ATTR_NAME = fclass
    ATTR_VALUES = <Empty>,<Missing>,<Null>,<Unfiltered>,primary,secondary,tertiary,residential,unclassified,track,motorway,trunk,unclassified;tra
    primary -> AttributeRemover_4
    secondary -> AttributeRemover_4
    tertiary -> AttributeRemover_4
    residential -> AttributeRemover_4
    unclassified -> AttributeRemover_4
    track -> AttributeRemover_4
    motorway -> AttributeRemover_4
    trunk -> AttributeRemover_4
AttributeRemover_4
    REMOVE_ATTRS = name,code,fclass,ref,layer,oneway,osm_id,maxspeed,tunnel,bridge
    -> B_0-1000_n_2
gis_osm_railways_free_1 (reader ESRISHAPE_1)
    attributes: osm_id char(10), code short, fclass char(28), name char(100)
    -> AttributeRemover_3
AttributeRemover_3
    REMOVE_ATTRS = name,code,fclass,osm_id
    -> B_0-1000_n_2
gis_osm_waterways_free_1 (reader ESRISHAPE_2)
    attributes: osm_id char(10), code short, fclass char(28), width long, name char(100)
    -> AttributeFilter
AttributeFilter
    ATTR_NAME = fclass
    ATTR_VALUES = <Empty>,<Missing>,<Null>,<Unfiltered>,canal
    canal -> AttributeRemover_6
AttributeRemover_6
    REMOVE_ATTRS = name,code,fclass,osm_id,width
    -> B_0-1000_n_2
gis_osm_landuse_a_free_1 (reader ESRISHAPE_3)
    attributes: osm_id char(10), code short, fclass char(28), name char(100)
    -> AttributeFilter_3
AttributeFilter_3
    ATTR_NAME = fclass
    ATTR_VALUES = <Empty>,<Missing>,<Null>,<Unfiltered>,industrial,reservoir,military,farmland,residential,orchard,commercial,quarry,farmyard,salt_pond
    industrial -> AttributeRemover_5
    reservoir -> AttributeRemover_5
    military -> AttributeRemover_5
    farmland -> AttributeRemover_5
    residential -> AttributeRemover_5
    orchard -> AttributeRemover_5
    commercial -> AttributeRemover_5
    quarry -> AttributeRemover_5
    farmyard -> AttributeRemover_5
    salt_pond -> AttributeRemover_5
AttributeRemover_5
    REMOVE_ATTRS = name,osm_id
    -> B_0-1000_n_2

Bookmark: Prepare country polygon
ne_10m_admin_0_countries (reader SHAPE_1)
    attributes: scalerank number(4,0), featurecla char(30), LABELRANK number(6,2), SOVEREIGNT char(32), SOV_A3 char(3), ADM0_DIF number(4,2), LEVEL number(4,2), TYPE char(17), ADMIN char(40), ADM0_A3 char(3), GEOU_DIF number(4,2), GEOUNIT char(40), GU_A3 char(3), SU_DIF number(4,2), SUBUNIT char(40), SU_A3 char(3), BRK_DIFF number(4,2), NAME char(36), NAME_LONG char(40), BRK_A3 char(3), BRK_NAME char(36), BRK_GROUP char(30), ABBREV char(13), POSTAL char(4), FORMAL_EN char(52), FORMAL_FR char(35), NOTE_ADM0 char(22), NOTE_BRK char(164), NAME_SORT char(36), NAME_ALT char(38),
      MAPCOLOR7 number(4,2), MAPCOLOR8 number(4,2), MAPCOLOR9 number(4,2), MAPCOLOR13 number(6,2), POP_EST number(13,2), GDP_MD_EST number(11,2), POP_YEAR number(7,2), LASTCENSUS number(7,2), GDP_YEAR number(7,2), ECONOMY char(26), INCOME_GRP char(23), WIKIPEDIA number(6,2), FIPS_10_ char(3), ISO_A2 char(5), ISO_A3 char(3), ISO_N3 char(3), UN_A3 char(4), WB_A2 char(3), WB_A3 char(3), WOE_ID number(11,2), WOE_ID_EH number(11,2), WOE_NOTE char(190), ADM0_A3_IS char(3), ADM0_A3_US char(3), ADM0_A3_UN number(6,2), ADM0_A3_WB number(6,2), CONTINENT char(23), REGION_UN char(23), SUBREGION char(25), REGION_WB char(26),
      NAME_LEN number(5,2), LONG_LEN number(5,2), ABBREV_LEN number(5,2), TINY number(6,2), HOMEPART number(6,2)
    -> AttributeFilter_4
Note: Country polygons are filtered. The country one wants to analyse is filtered, the unfildered ones (outside) are then forwardet to clip against the country polygon at a later stage.
AttributeFilter_4
    ATTR_NAME = SOV_A3
    ATTR_VALUES = <Empty>,<Missing>,<Null>,<Unfiltered>,NOR
    NOR -> AttributeRemover_7
    <UNFILTERED> -> AttributeRemover_9
AttributeRemover_7
    REMOVE_ATTRS = ABBREV,ABBREV_LEN,ADM0_A3,ADM0_A3_IS,ADM0_A3_UN,ADM0_A3_US,ADM0_A3_WB,ADM0_DIF,ADMIN,BRK_A3,BRK_DIFF,BRK_GROUP,BRK_NAME,CONTINENT,ECONOMY,featurecla,FIPS_10_,FORMAL_EN,FORMAL_FR,GDP_MD_EST,GDP_YEAR,GEOU_DIF,GEOUNIT,GU_A3,HOMEPART,INCOME_GRP,ISO_A2,ISO_A3,ISO_N3,LABELRANK,LASTCENSUS,LEVEL,LONG_LEN,MAPCOLOR7,MAPCOLOR8,MAPCOLOR9,MAPCOLOR13,NAME,NAME_ALT,NAME_LEN,NAME_LONG,NAME_SORT,NOTE_ADM0,NOTE_BRK,POP_EST,POP_YEAR,POSTAL,REGION_UN,REGION_WB,scalerank,SOV_A3,SOVEREIGNT,SU_A3,SU_DIF,SUBREGION,SUBUNIT,TINY,TYPE,UN_A3,WB_A2,WB_A3,WIKIPEDIA,WOE_ID,WOE_ID_EH,WOE_NOTE
    -> AreaOnAreaOverlayer [AREA]
AttributeRemover_9
    REMOVE_ATTRS = fclass,SU_DIF,ISO_N3,ISO_A3,NAME,code,MAPCOLOR7,NOTE_ADM0,GDP_YEAR,GEOUNIT,featurecla,UN_A3,NAME_ALT,CONTINENT,ADM0_DIF,ABBREV_LEN,ADM0_A3_UN,INCOME_GRP,ADM0_A3_US,BRK_A3,MAPCOLOR8,SUBUNIT,GU_A3,FIPS_10_,ADM0_A3,GEOU_DIF,name,ABBREV,ECONOMY,FORMAL_FR,POSTAL,LEVEL,osm_id,POP_YEAR,NOTE_BRK,SOVEREIGNT,GDP_MD_EST,SOV_A3,WOE_ID_EH,ADMIN,HOMEPART,WOE_ID,ADM0_A3_WB,LABELRANK,scalerank,SUBREGION,WIKIPEDIA,LASTCENSUS,NAME_LEN,BRK_GROUP,BRK_NAME,POP_EST,TINY,TYPE,BRK_DIFF,NAME_LONG,WB_A3,SU_A3,REGION_UN,LONG_LEN,MAPCOLOR9,WB_A2,NAME_SORT,ADM0_A3_IS,REGION_WB,FORMAL_EN,ISO_A2,MAPCOLOR13,WOE_NOTE
    -> AreaOnAreaOverlayer_2 [AREA]

Bookmark: Establish encroachment areas
Dissolver_2
    ACCUM_INPUT_ATTRS = Drop Incoming Attributes
    CLEANING_TOLERANCE = None
    CONNECT_Z_MODE = First Wins
    DEAGGREGATE_INPUT = Yes
    AREA -> Clipper [CLIPPER]
    AREA -> AttributeCreator
    AREA -> B_1000-3000_s2_3
AttributeCreator
    ATTR_LIST = wzone,n
    -> AttributeRemover
Note: Buffering 2000 more meters based on 1000 buffer start.
B_1000-3000_s2_3: GeographicBufferer
    ANGLE = 22.5
    BufferDist = 2000
    BufferUnit = Meters
    CAP_STYLE = Round
    CORNER_STYLE = Round
    MITER_LIMIT = 1
    -> Dissolver_3
Dissolver_3
    ACCUM_INPUT_ATTRS = Drop Incoming Attributes
    CLEANING_TOLERANCE = None
    CONNECT_Z_MODE = First Wins
    DEAGGREGATE_INPUT = Yes
    AREA -> 3000-5000_s1_3
    AREA -> Clipper_2 [CLIPPER]
    AREA -> Clipper [CLIPPEE]
3000-5000_s1_3: GeographicBufferer
    ANGLE = 22.5
    BufferDist = 2000
    BufferUnit = Meters
    CAP_STYLE = Round
    CORNER_STYLE = Round
    MITER_LIMIT = 1
    -> Dissolver_5
Dissolver_5
    ACCUM_INPUT_ATTRS = Drop Incoming Attributes
    CLEANING_TOLERANCE = None
    CONNECT_Z_MODE = First Wins
    DEAGGREGATE_INPUT = Yes
    AREA -> Clipper_2 [CLIPPEE]
Clipper_2
    BOUNDARY_CASES = Treat as Inside
    CLEANING_TOLERANCE = None
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clipper and Clippee
    OUTSIDE -> AttributeCreator_2
AttributeCreator_2
    ATTR_TABLE = SET_TO wzone = 1
    -> Diss_2
Diss_2: Dissolver
    ACCUM_INPUT_ATTRS = Drop Incoming Attributes
    CLEANING_TOLERANCE = None
    CONNECT_Z_MODE = First Wins
    DEAGGREGATE_INPUT = Yes
    GROUP_BY = wzone
    AREA -> AttributeRemover
Note: Near (N) buffer 0-1000 meters is clipped againstsecond buffer 1000-2000
Clipper
    BOUNDARY_CASES = Treat as Inside
    CLEANING_TOLERANCE = None
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clipper and Clippee
    OUTSIDE -> AttributeCreator_3
AttributeCreator_3
    ATTR_TABLE = SET_TO wzone = 2
    -> AttributeRemover
AttributeRemover
    REMOVE_ATTRS = id,zoomlevel,secretkey,addedtime,navn,epost,anonym,godkjent,_clipped,_fme_no_clipper
    -> Dissolver_4
Dissolver_4
    ACCUM_INPUT_ATTRS = Drop Incoming Attributes
    CLEANING_TOLERANCE = None
    CONNECT_Z_MODE = First Wins
    DEAGGREGATE_INPUT = Yes
    GROUP_BY = wzone
    AREA -> GeographicAreaCalculator_2
    AREA -> AreaOnAreaOverlayer [AREA]

Bookmark: Wilderness areas (what are left is not encroachment areas)
AreaOnAreaOverlayer
    ACCUM_ATTRS_NAME = Use Attributes From One Feature
    CLEANING_TOLERANCE = None
    CONNECT_Z_MODE = First Wins
    DEAGGREGATE_INPUT = Yes
    OVC_ATTR = _overlaps
    AREA -> AttributeFilter_5
AttributeFilter_5
    ATTR_NAME = _overlaps
    ATTR_VALUES = <Empty>,<Missing>,<Null>,<Unfiltered>,1
    1 -> AttributeRemover_2
AttributeRemover_2
    REMOVE_ATTRS = _overlaps
    -> AttributeCreator_4
AttributeCreator_4
    ATTR_TABLE = SET_TO wzone = w
    -> GeographicAreaCalculator_2

Bookmark: Outside remover
AreaOnAreaOverlayer_2
    ACCUM_ATTRS_NAME = Use Attributes From One Feature
    CLEANING_TOLERANCE = None
    CONNECT_Z_MODE = First Wins
    DEAGGREGATE_INPUT = Yes
    OVC_ATTR = _overlaps
    AREA -> AttributeFilter_6
AttributeFilter_6
    ATTR_NAME = _overlaps
    ATTR_VALUES = <Empty>,<Missing>,<Null>,<Unfiltered>,1
    1 -> AttributeRemover_10
AttributeRemover_10
    REMOVE_ATTRS = _overlaps
    -> Tester
Tester
    BOOL_OP = OR
    TEST_CLAUSE:
      TEST @Value(wzone) = 1
      TEST @Value(wzone) = 2
      TEST @Value(wzone) = w
      TEST @Value(wzone) = n
    TEST_MODE = TEST
    PASSED -> Result_of_calculations
    PASSED -> wilderness (writer GEOPACKAGE_1)
