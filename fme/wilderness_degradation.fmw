FME workspace wilderness_degradation.fmw

Parameters:
- DestDataset_SHAPE = $(FME_MF_DIR)resultat   # Destination Esri Shape Directory
- DestDataset_XLSXW2_4 = $(FME_MF_DIR)resultat\inon_tap.xlsx   # Destination Microsoft Excel File
- SourceDataset_FILEGDB = $(FME_MF_DIR)resultat\wilderness_bulgaria.gdb   # Source Geodatabase
- FEATURE_TYPES =
- SourceDataset_SHAPE = $(FME_MF_DIR)datagrunnlag\bulgaria\encroachment_road.shp   # Source Esri Shape File(s)
- FEATURE_TYPES_2 =
- DestDataset_FILEGDB = $(FME_MF_DIR)result\wilderness_change_bulgaria.gdb   # Destination Geodatabase

Readers:
- FILEGDB_1: FILEGDB from $(SourceDataset_FILEGDB)
- SHAPE_1: SHAPE from $(SourceDataset_SHAPE)

Writers:
- SHAPE_2: SHAPE to $(DestDataset_SHAPE)
- XLSXW2_1: XLSXW2 to $(DestDataset_XLSXW2_4)
- FILEGDB_2: FILEGDB to $(DestDataset_FILEGDB)

Note: encroachment data
new_road (reader SHAPE_1)
    attributes: id number(10,0)
    -> 0-1000_n
    -> 10000_m_surroundings
0-1000_n: GeographicBufferer
    BufferDist = 1000
    BufferUnit = Meters
    CAP_STYLE = Round
    -> Clipper_2 [input 1]
    -> 1000-3000_s2_2
1000-3000_s2_2: GeographicBufferer
    BufferDist = 2000
    BufferUnit = Meters
    CAP_STYLE = Round
    -> Clipper [input 1]
    -> 3000-5000_s1_2
3000-5000_s1_2: GeographicBufferer
    BufferDist = 2000
    BufferUnit = Meters
    CAP_STYLE = Round
    -> Clipper [input 2]
Clipper
    CREATE_AGGREGATES = Yes
    CLIPPED_ATTR = _clipped
    MERGE_ATTRS = No
    PRESERVE_CLIPPEE_EXTENTS = No
    ATTR_PREFIX = clipper_
    CLIP_TYPE = Multiple Clippers
    BOUNDARY_CASES = Treat as Inside
    INSIDE -> Clipper_2 [input 2]
    OUTSIDE -> AttributeCreator_3
AttributeCreator_3
    ATTR_LIST = wzone_after,1
    -> AttributeRemover
Clipper_2
    CREATE_AGGREGATES = Yes
    CLIPPED_ATTR = _clipped
    MERGE_ATTRS = No
    PRESERVE_CLIPPEE_EXTENTS = No
    ATTR_PREFIX = clipper_
    CLIP_TYPE = Multiple Clippers
    BOUNDARY_CASES = Treat as Inside
    INSIDE -> AttributeCreator
    OUTSIDE -> AttributeCreator_2
AttributeCreator
    ATTR_LIST = wzone_after,n
    -> AttributeRemover
AttributeCreator_2
    ATTR_LIST = wzone_after,2
    -> AttributeRemover
AttributeRemover
    REMOVE_ATTRS = zoomlevel,secretkey,navn,epost,anonym,_clipped,_fme_no_clipper
    -> AreaOnAreaOverlayer
10000_m_surroundings: GeographicBufferer
    BufferDist = 10000
    BufferUnit = Meters
    CAP_STYLE = Square
    -> Clipper_3 [input 1]
Note: wilderness data set
wilderness (reader FILEGDB_1)
    attributes: wzone text(10), area_km2 double, OBJECTID objectid
    -> Clipper_3 [input 2]
Clipper_3
    CREATE_AGGREGATES = Yes
    CLIPPED_ATTR = _clipped
    MERGE_ATTRS = No
    PRESERVE_CLIPPEE_EXTENTS = No
    ATTR_PREFIX = clipper_
    CLIP_TYPE = Multiple Clippers
    BOUNDARY_CASES = Treat as Inside
    INSIDE -> AreaOnAreaOverlayer
AreaOnAreaOverlayer
    OVC_ATTR = _overlaps
    AREA -> GeographicAreaCalculator
GeographicAreaCalculator
    AREA_ATTR = area_km2
    AreaMult = 0.000001
    BUFFERED -> remove_attibutes
remove_attibutes: AttributeRemover
    REMOVE_ATTRS = id,OBJECTID,_clipped,_overlaps
    -> INON_filter_kombinasjoner
INON_filter_kombinasjoner: INON filter kombinasjoner
    WZONE_AFTER = @Value(wzone_after)
    WZONE = @Value(wzone)
    null-1_1 -> AttributeCreator_5
    null-n_n -> AttributeCreator_5
    null-w_w -> AttributeCreator_5
    1-w_w -> AttributeCreator_5
    n-w_w -> AttributeCreator_5
    n-1_1 -> AttributeCreator_5
    2-1_1 -> AttributeCreator_5
    2-w_w -> AttributeCreator_5
    n-2_2 -> AttributeCreator_5
    null-2_2 -> AttributeCreator_5
    null-null_null -> AttributeCreator_4
    w-w_w -> AttributeCreator_4
    1-1_1 -> AttributeCreator_4
    n-n_n -> AttributeCreator_4
    2-2_2 -> AttributeCreator_4
    2-null__null -> AttributeCreator_6
    w-n_n -> AttributeCreator_6
    n-null_null -> AttributeCreator_6
    w-null_null -> AttributeCreator_6
    2-n_n -> AttributeCreator_6
    1-n_n -> AttributeCreator_6
    w-1_1 -> AttributeCreator_6
    1-null__null -> AttributeCreator_6
    1-2_2 -> AttributeCreator_6
    w-2_2 -> AttributeCreator_6
AttributeCreator_5
    ATTR_LIST = tablename,wilderness_increase
    -> NewFeatureType (writer FILEGDB_2)
NewFeatureType (writer FILEGDB_2)
    attributes: wzone text(10), wzone_after text(10), area_km2 double
AttributeCreator_4
    ATTR_LIST = tablename,wilderness_nochange
    -> NewFeatureType00 (writer FILEGDB_2)
NewFeatureType00 (writer FILEGDB_2)
    attributes: wzone text(10), wzone_after text(10), area_km2 double
AttributeCreator_6
    ATTR_LIST = tablename,wilderness_degradation
    -> NewFeatureType01 (writer FILEGDB_2)
NewFeatureType01 (writer FILEGDB_2)
    attributes: wzone text(10), wzone_after text(10), area_km2 double

FME custom transformer INON filter kombinasjoner

Parameters:
- WZONE = @Value(wzone)   # wzone
- WZONE_AFTER = @Value(wzone_after)   # Wzone After

AttributeFilter_Input (input)
    -> AttributeFilter
AttributeFilter
    ATTR_NAME = wzone
    ATTR_VALUES = <EMPTY>,<MISSING>,<NULL>,<UNFILTERED>,w,1,2,n
    1 -> 1-w
    1 -> 1-1
    1 -> 1-2
    1 -> 1-n
    1 -> 1-null
    2 -> 2-w
    2 -> 2-1
    2 -> 2-2
    2 -> 2-n
    2 -> 2-null
    <NULL> -> null-1
    <NULL> -> null-2
    <NULL> -> null-n
    <NULL> -> null-null
    w -> V-V
    w -> w-1
    w -> w-2
    w -> w-n
    w -> V-null
    n -> n-w
    n -> n-n
    n -> n-null
    n -> n-2_2
    n -> N-1
    <NULL> -> null-V
null-V: AttributeFilter
    ATTR_NAME = wzone_after
    ATTR_VALUES = <EMPTY>,<MISSING>,<NULL>,<UNFILTERED>,w
    w -> null-w_w (output)
null-w_w (output)
n-w: AttributeFilter
    ATTR_NAME = wzone_after
    ATTR_VALUES = <EMPTY>,<MISSING>,<NULL>,<UNFILTERED>,w
    w -> n-w_w (output)
n-w_w (output)
V-V: AttributeFilter
    ATTR_NAME = wzone_after
    ATTR_VALUES = <EMPTY>,<MISSING>,<NULL>,<UNFILTERED>,w
    w -> w-w_w (output)
w-w_w (output)
2-w: AttributeFilter
    ATTR_NAME = wzone_after
    ATTR_VALUES = <EMPTY>,<MISSING>,<NULL>,<UNFILTERED>,w
    w -> 2-w_w (output)
2-w_w (output)
1-w: AttributeFilter
    ATTR_NAME = wzone
    ATTR_VALUES = <EMPTY>,<MISSING>,<NULL>,<UNFILTERED>,w
    w -> 1-w_w (output)
1-w_w (output)
null-1: AttributeFilter
    ATTR_NAME = wzone_after
    ATTR_VALUES = <EMPTY>,<MISSING>,<NULL>,<UNFILTERED>,1
    1 -> null-1_1 (output)
null-1_1 (output)
N-1: AttributeFilter
    ATTR_NAME = wzone_after
    ATTR_VALUES = <EMPTY>,<MISSING>,<NULL>,<UNFILTERED>,1
    1 -> n-1_1 (output)
n-1_1 (output)
1-1: AttributeFilter
    ATTR_NAME = wzone_after
    ATTR_VALUES = <EMPTY>,<MISSING>,<NULL>,<UNFILTERED>,1
    1 -> 1-1_1 (output)
1-1_1 (output)
2-1: AttributeFilter
    ATTR_NAME = wzone_after
    ATTR_VALUES = <EMPTY>,<MISSING>,<NULL>,<UNFILTERED>,1
    1 -> 2-1_1 (output)
2-1_1 (output)
w-1: AttributeFilter
    ATTR_NAME = wzone_after
    ATTR_VALUES = <EMPTY>,<MISSING>,<NULL>,<UNFILTERED>,1
    1 -> w-1_1 (output)
w-1_1 (output)
null-2: AttributeFilter
    ATTR_NAME = wzone_after
    ATTR_VALUES = <EMPTY>,<MISSING>,<NULL>,<UNFILTERED>,2
    2 -> null-2_2 (output)
null-2_2 (output)
n-2_2: AttributeFilter
    ATTR_NAME = wzone_after
    ATTR_VALUES = <EMPTY>,<MISSING>,<NULL>,<UNFILTERED>,2
    2 -> n-2_2 (output)
n-2_2 (output)
2-2: AttributeFilter
    ATTR_NAME = wzone_after
    ATTR_VALUES = <EMPTY>,<MISSING>,<NULL>,<UNFILTERED>,2
    2 -> 2-2_2 (output)
2-2_2 (output)
1-2: AttributeFilter
    ATTR_NAME = wzone_after
    ATTR_VALUES = <EMPTY>,<MISSING>,<NULL>,<UNFILTERED>,2
    2 -> 1-2_2 (output)
1-2_2 (output)
w-2: AttributeFilter
    ATTR_NAME = wzone_after
    ATTR_VALUES = <EMPTY>,<MISSING>,<NULL>,<UNFILTERED>,2
    2 -> w-2_2 (output)
w-2_2 (output)
n-n: AttributeFilter
    ATTR_NAME = wzone_after
    ATTR_VALUES = <EMPTY>,<MISSING>,<NULL>,<UNFILTERED>,n
    n -> n-n_n (output)
n-n_n (output)
w-n: AttributeFilter
    ATTR_NAME = wzone_after
    ATTR_VALUES = <EMPTY>,<MISSING>,<NULL>,<UNFILTERED>,n
    n -> w-n_n (output)
w-n_n (output)
1-n: AttributeFilter
    ATTR_NAME = wzone_after
    ATTR_VALUES = <EMPTY>,<MISSING>,<NULL>,<UNFILTERED>,n
    n -> 1-n_n (output)
1-n_n (output)
null-n: AttributeFilter
    ATTR_NAME = wzone_after
    ATTR_VALUES = <EMPTY>,<MISSING>,<NULL>,<UNFILTERED>,N
    N -> null-n_n (output)
null-n_n (output)
2-n: AttributeFilter
    ATTR_NAME = wzone_after
    ATTR_VALUES = <EMPTY>,<MISSING>,<NULL>,<UNFILTERED>,n
    n -> 2-n_n (output)
2-n_n (output)
V-null: AttributeFilter
    ATTR_NAME = wzone_after
    ATTR_VALUES = <EMPTY>,<MISSING>,<NULL>,<UNFILTERED>
    <NULL> -> w-null_null (output)
w-null_null (output)
1-null: AttributeFilter
    ATTR_NAME = wzone_after
    ATTR_VALUES = <EMPTY>,<MISSING>,<NULL>,<UNFILTERED>
    <NULL> -> 1-null__null (output)
1-null__null (output)
n-null: AttributeFilter
    ATTR_NAME = wzone_after
    ATTR_VALUES = <EMPTY>,<MISSING>,<NULL>,<UNFILTERED>
    <NULL> -> n-null_null (output)
n-null_null (output)
2-null: AttributeFilter
    ATTR_NAME = wzone_after
    ATTR_VALUES = <EMPTY>,<MISSING>,<NULL>,<UNFILTERED>
    <NULL> -> 2-null__null (output)
2-null__null (output)
null-null: AttributeFilter
    ATTR_NAME = wzone_after
    ATTR_VALUES = <EMPTY>,<MISSING>,<NULL>,<UNFILTERED>
    <NULL> -> null-null_null (output)
null-null_null (output)
