FME workspace inon_calculation_norway.fmw

Parameters:
- DestDataset_SHAPE = $(FME_MF_DIR)resultat   # Destination Esri Shape Directory
- DestDataset_XLSXW2_4 = $(FME_MF_DIR)resultat\inon_tap.xlsx   # Destination Microsoft Excel File
- DestDataset_XLSXW2 = $(FME_MF_DIR)resultat\inon_tap_pivot.xlsx   # Destination Microsoft Excel File
- SourceDataset_FILEGDB = $(FME_MF_DIR)datagrunnlag\norge\FKB_Vegnett.gdb   # Source Geodatabase
- SourceDataset_SHAPE = $(FME_MF_DIR)datagrunnlag\norge\landflate\landflate_hel.shp   # Source Esri Shape File(s)
- DestDataset_FILEGDB = $(FME_MF_DIR)result\wilderness_norway.gdb   # Destination Geodatabase

Readers:
- FILEGDB_1: FILEGDB from $(SourceDataset_FILEGDB) in UTM84-33N
- SHAPE_1: SHAPE from $(SourceDataset_SHAPE)

Writers:
- SHAPE_2: SHAPE to $(DestDataset_SHAPE)
- XLSXW2_1: XLSXW2 to $(DestDataset_XLSXW2_4)
- XLSXW2_2: XLSXW2 to $(DestDataset_XLSXW2)
- FILEGDB_2: FILEGDB to $(DestDataset_FILEGDB)

Note: Inngrepsdata legges inn her
vegnett_linje (reader FILEGDB_1)
    attributes: OBJECTID objectid, objtype text(80), vegkategori text(80), vegstatus text(80), vegnummer int, hovedparsell int, veglenkemeterfra int, veglenkemetertil int, veglenkefradato date, feltoversikt text(80), gatenavn text(80), gatenummer int, kommunenummer int, datafangstdato date, verifiseringsdato date, malemetode int, noyaktighet int, synbarhet int, h_malemetode int, h_noyaktighet int, maksimaltavvik int, medium text(80), omradeid int, originaldatavert text(80), kopidato date, SHAPE_Length double
    -> AttributeFilter_2
AttributeFilter_2
    ATTR_NAME = vegkategori
    ATTR_VALUES = <EMPTY>,<MISSING>,<NULL>,<UNFILTERED>,E,F,K,P,R,S
    E -> AttributeRemover_4
    F -> AttributeRemover_4
    K -> AttributeRemover_4
    P -> AttributeRemover_4
    R -> AttributeRemover_4
    S -> AttributeRemover_4
AttributeRemover_4
    REMOVE_ATTRS = OBJECTID,objtype,vegkategori,vegstatus,vegnummer,hovedparsell,veglenkemeterfra,veglenkemetertil,veglenkefradato,feltoversikt,gatenavn,gatenummer,kommunenummer,datafangstdato,verifiseringsdato,malemetode,noyaktighet,synbarhet,h_malemetode,h_noyaktighet,maksimaltavvik,medium,omradeid,originaldatavert,kopidato,SHAPE_Length
    -> Aggregator
Aggregator
    ORDERED = No
    MODE = Geometry - Assemble One Level
    SEP = ,
    ACCUM_ATTRS_NAME = No
    AGGREGATE_TYPE = Homogeneous Collection (If Possible)
    AGGREGATE -> B_0-1000_n
B_0-1000_n: GeographicBufferer
    BufferDist = 1000
    CAP_STYLE = Round
    BufferUnit = Meters
    -> Dissolver_2
Dissolver_2
    ACCUM_INPUT_ATTRS = No
    NO_OVRLP = No
    AREA -> B_1000-3000_s2_2
    AREA -> Clipper [input 1]
    AREA -> AttributeCreator
AttributeCreator
    ATTR_LIST = inonsone,N
    -> AttributeRemover
B_1000-3000_s2_2: GeographicBufferer
    BufferDist = 2000
    CAP_STYLE = Round
    BufferUnit = Meters
    -> Dissolver_3
Dissolver_3
    ACCUM_INPUT_ATTRS = No
    NO_OVRLP = No
    AREA -> 3000-5000_s1_2
    AREA -> Clipper_2 [input 1]
    AREA -> Clipper [input 2]
3000-5000_s1_2: GeographicBufferer
    BufferDist = 2000
    CAP_STYLE = Round
    BufferUnit = Meters
    -> Dissolver_5
Dissolver_5
    ACCUM_INPUT_ATTRS = No
    NO_OVRLP = No
    AREA -> Clipper_2 [input 2]
Clipper_2
    CLIPPED_ATTR = _clipped
    BOUNDARY_CASES = Treat as Inside
    CREATE_AGGREGATES = Yes
    PRESERVE_CLIPPEE_EXTENTS = No
    MERGE_ATTRS = No
    CLIP_TYPE = Multiple Clippers
    OUTSIDE -> AttributeCreator_2
AttributeCreator_2
    ATTR_LIST = inonsone,1
    -> Diss_2
Diss_2: Dissolver
    GROUP_BY = inonsone
    ACCUM_INPUT_ATTRS = No
    NO_OVRLP = No
    AREA -> AttributeRemover
Clipper
    CLIPPED_ATTR = _clipped
    BOUNDARY_CASES = Treat as Inside
    CREATE_AGGREGATES = Yes
    PRESERVE_CLIPPEE_EXTENTS = No
    MERGE_ATTRS = No
    CLIP_TYPE = Multiple Clippers
    OUTSIDE -> AttributeCreator_3
AttributeCreator_3
    ATTR_LIST = inonsone,2
    -> AttributeRemover
AttributeRemover
    REMOVE_ATTRS = id,zoomlevel,secretkey,addedtime,navn,epost,anonym,godkjent,_clipped,_fme_no_clipper
    -> Dissolver_4
Dissolver_4
    GROUP_BY = inonsone
    ACCUM_INPUT_ATTRS = No
    NO_OVRLP = No
    AREA -> GeographicAreaCalculator
    AREA -> Clipper_3
Clipper_3
    CLIPPED_ATTR = _clipped
    BOUNDARY_CASES = Treat as Inside
    CREATE_AGGREGATES = Yes
    PRESERVE_CLIPPEE_EXTENTS = No
    MERGE_ATTRS = No
    CLIP_TYPE = Multiple Clippers
    OUTSIDE -> AttributeRemover_2
    OUTSIDE -> Inspector
AttributeRemover_2
    REMOVE_ATTRS = REGION_,REGION_ID,AREA,PERIMETER,OPPR,X,Y,KOORDH,FTEMA,SENTER,MALEMETODE,NOYAKTIGHE,SYNBARHET,H_MALEMETO,H_NOYAKTIG,MAX_AVVIK,DATO,KOMM,NAVN,Shape_Leng,Shape_Area,inonsoneet,_clipped,_fme_no_clipper,FIPS,ISO2,ISO3,UN,NAME,POP2005,REGION,SUBREGION,LON,LAT,id,zoomlevel,secretkey,addedtime,navn,epost,anonym,godkjent
    -> AttributeCreator_4
AttributeCreator_4
    ATTR_LIST = inonsone,V
    -> GeographicAreaCalculator
GeographicAreaCalculator
    AreaMult = 0.000001
    AREA_ATTR = areal_km2
    BUFFERED -> alle_tapte
    BUFFERED -> Inspector_2
Inspector_2
alle_tapte: AttributeRemover
    REMOVE_ATTRS = id,addedtime,godkjent,inonid,periodesta,periodeslu,inonsonefø,inonsektor,inonendrin,_clipped,_overlaps,zoomlevel,secretkey,navn,epost,anonym,_fme_no_clipper
    -> AreaOnAreaOverlayer
    -> wilderness_raw (writer FILEGDB_2)
wilderness_raw (writer FILEGDB_2)
    attributes: inonsone text(10), areal_km2 text(10)
Inspector
Note: Landflate legges inn her
landflate_hel (reader SHAPE_1)
    attributes: REGION_ number(19,11), REGION_ID number(19,11), AREA number(19,11), PERIMETER number(19,11), OPPR number(4,0), X number(19,11), Y number(19,11), KOORDH number(19,11), FTEMA number(4,0), SENTER char(9), MALEMETODE number(4,0), NOYAKTIGHE number(9,0), SYNBARHET number(4,0), H_MALEMETO number(4,0), H_NOYAKTIG number(9,0), MAX_AVVIK number(9,0), DATO date, KOMM number(4,0), NAVN char(60), Shape_Leng number(19,11), Shape_Area number(19,11), inonsoneet char(3)
    -> AreaOnAreaOverlayer
AreaOnAreaOverlayer
    OVC_ATTR = _overlaps
    AREA -> er_landflate
    AREA -> AreaOnAreaOverlayer_Area
AreaOnAreaOverlayer_Area: Inspector
er_landflate: Tester
    TEST_DESCRIPTION = ""
    BOOL_OP = OR
    TEST_CLAUSE = TEST @Value(FTEMA) = 4002
    TEST_MODE = Automatic
    PASSED -> er_inon
er_inon: Tester
    TEST_DESCRIPTION = ""
    BOOL_OP = OR
    TEST_CLAUSE:
      TEST @Value(inonsoneet) = 1
      TEST @Value(inonsoneet) = 2
      TEST @Value(inonsoneet) = N
    TEST_MODE = Automatic
    PASSED -> AttributeRemover_3
    FAILED -> AttributeCreator_5
AttributeCreator_5
    ATTR_LIST = inonsoneet,V
    -> AttributeRemover_3
AttributeRemover_3
    REMOVE_ATTRS = _overlaps,AREA,DATO,FTEMA,H_MALEMETO,H_NOYAKTIG,inonsone,KOORDH,MALEMETODE,MAX_AVVIK,NAVN,NOYAKTIGHE,OPPR,PERIMETER,REGION_,REGION_ID,SENTER,Shape_Area,Shape_Leng,SYNBARHET,X,Y
    -> wilderness (writer FILEGDB_2)
    -> Result_of_calculations
Result_of_calculations: Inspector
wilderness (writer FILEGDB_2)
    attributes: inonsone text(10), areal_km2 text(10), KOMM text(10)
